module acl-service {

  namespace "http://example.com/acl-service";
  prefix acl-service;

  import ietf-inet-types {
    prefix inet;
  }
  import tailf-common {
    prefix tailf;
  }
  import tailf-ncs {
    prefix ncs;
  }

  description
    "A simple access list module";

  revision 2022-06-03 {
    description
      "Initial revision.";
  }

  list access-list {
    description "A basic access-list definition";

    key name;
    // TODO: ACL names can NOT have whitespace
    leaf name {
      tailf:info "Unique name for this access-list";
      tailf:cli-allow-range;
      type string; 
    }

    uses ncs:service-data;
    ncs:servicepoint acl-service-servicepoint;

    leaf-list device {
      tailf:info "The devices where this ACL will be created";
      type leafref {
        path "/ncs:devices/ncs:device/ncs:name";
      }
    }

    container default {
      tailf:info "Default behaviors for the ACL";
      leaf rule { 
        tailf:info "Whether the ACL will end with a default deny or permit";
        // TODO: Only the valus of "deny" or "permit" should be allowed
        type string;
        default deny;
      }
    }

    list rule {
      tailf:info "The list of rules in this access-list";
      ordered-by user;
      key name; 

      // TODO: Rule names can NOT have whitespace
      leaf name {
        tailf:info "The name for this rule.";
        type string;
      }

      leaf description {
        tailf:info "The purpose for this rule in the access-list";
        type string; 
      }

      leaf action {
        mandatory true;
        tailf:info "Whether this rule is to deny or permit traffic";
        // TODO: Only the valus of "deny" or "permit" should be allowed
        type string;
      }

      leaf protocol { 
        mandatory true;
        tailf:info "tcp/udp";
        // TODO: Only the valus of "tcp" or "udp" should be allowed
        type string;
      }

      container source {
        tailf:info "The source details for this rule";

        leaf address {
          mandatory true;
          tailf:info "The source address for this rule";
          // TODO: allow IPv4 address or prefix based on ietf-inet-types
          type string;
        }

        leaf port {
          tailf:info "The source port (if different from destination) for this rule";
          type uint16;
        }
      }

      container destination {
        tailf:info "The destination details for this rule";

        leaf address {
          mandatory true;
          tailf:info "The destination address for this rule";
          // TODO: allow IPv4 address or prefix based on ietf-inet-types
          type string;
        }

        leaf port {
          mandatory true;
          tailf:info "The destination port for this rule";
          // TODO: Only allow well known ports (1 - 1024)
          type uint16;
        }
      }

      leaf log {
        tailf:info "Whether to log hits to this rule";
        // TODO: The log leaf should either be present or not
        type string;
      }

    }
  }
}
